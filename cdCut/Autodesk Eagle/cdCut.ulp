/*
- Open Eagle
- Add path unter Optionen=>Verzeichnisse=>User-Language-Programme
- Open an empty board
- type "run cdCut" in cmd-line
*/


#include "cmd.ulp"

int n;
string cmd;

cmdInit();

cmdAdd("grid mm");
cmdAdd("layer 1");
cmdAdd("set wire_bend 2;");
cmdAdd("set width 0.1");

cmdAdd("circle (0 0) (60 0)"); //aussendurchmesser
cmdAdd("circle (0 0) (18.5 0)"); //nutzbarer innendurchmesser
cmdAdd("circle (0 0) (7.5 0)"); //loch in der mitte

//squares
real squareA = 51; //rechteck seite a
real squareB = 35; //rechteck seite b
real offset;
real angle;

//basic square
real squareX[] = {squareA/2, -squareA/2, -squareA/2, squareA/2, squareA/2};
real squareY[] = {squareB/2, squareB/2, -squareB/2, -squareB/2, squareB/2};
real squareX_1[];
real squareY_1[];
real squareX_2[];
real squareY_2[];
real squareX_3[];
real squareY_3[];


//square 1
offset = 36;
squareX_1[0] = squareX[0];
squareX_1[1] = squareX[1];
squareX_1[2] = squareX[2];
squareX_1[3] = squareX[3];
squareX_1[4] = squareX[4];

squareY_1[0] = squareY[0] + offset;
squareY_1[1] = squareY[1] + offset;
squareY_1[2] = squareY[2] + offset;
squareY_1[3] = squareY[3] + offset;
squareY_1[4] = squareY[4] + offset;

for(n=0; n<4; n++){
	sprintf(cmd, "line (%f %f) (%f %f)", squareX_1[n], squareY_1[n], squareX_1[n+1], squareY_1[n+1]);
	cmdAdd(cmd);
}


//square 2
angle = 120.0 /360.0*2.0*PI;
squareX_2[0] = cos(angle)*squareX_1[0] - sin(angle)*squareY_1[0];
squareX_2[1] = cos(angle)*squareX_1[1] - sin(angle)*squareY_1[1];
squareX_2[2] = cos(angle)*squareX_1[2] - sin(angle)*squareY_1[2];
squareX_2[3] = cos(angle)*squareX_1[3] - sin(angle)*squareY_1[3];
squareX_2[4] = cos(angle)*squareX_1[4] - sin(angle)*squareY_1[4];

squareY_2[0] = sin(angle)*squareX_1[0] + cos(angle)*squareY_1[0];
squareY_2[1] = sin(angle)*squareX_1[1] + cos(angle)*squareY_1[1];
squareY_2[2] = sin(angle)*squareX_1[2] + cos(angle)*squareY_1[2];
squareY_2[3] = sin(angle)*squareX_1[3] + cos(angle)*squareY_1[3];
squareY_2[4] = sin(angle)*squareX_1[4] + cos(angle)*squareY_1[4];

for(n=0; n<4; n++){
	sprintf(cmd, "line (%f %f) (%f %f)", squareX_2[n], squareY_2[n], squareX_2[n+1], squareY_2[n+1]);
	cmdAdd(cmd);
}


//square 3
angle = 240.0 /360.0*2.0*PI;
squareX_3[0] = cos(angle)*squareX_1[0] - sin(angle)*squareY_1[0];
squareX_3[1] = cos(angle)*squareX_1[1] - sin(angle)*squareY_1[1];
squareX_3[2] = cos(angle)*squareX_1[2] - sin(angle)*squareY_1[2];
squareX_3[3] = cos(angle)*squareX_1[3] - sin(angle)*squareY_1[3];
squareX_3[4] = cos(angle)*squareX_1[4] - sin(angle)*squareY_1[4];

squareY_3[0] = sin(angle)*squareX_1[0] + cos(angle)*squareY_1[0];
squareY_3[1] = sin(angle)*squareX_1[1] + cos(angle)*squareY_1[1];
squareY_3[2] = sin(angle)*squareX_1[2] + cos(angle)*squareY_1[2];
squareY_3[3] = sin(angle)*squareX_1[3] + cos(angle)*squareY_1[3];
squareY_3[4] = sin(angle)*squareX_1[4] + cos(angle)*squareY_1[4];

for(n=0; n<4; n++){
	sprintf(cmd, "line (%f %f) (%f %f)", squareX_3[n], squareY_3[n], squareX_3[n+1], squareY_3[n+1]);
	cmdAdd(cmd);
}


/*string str;
output("sample"){
	printf(cmdGet());
}*/

exit(cmdGet());
